string basefilename;
string buf;
string ext = "png";
string file;
int c;
int res = 300;
int batch = 0;
int forcefile = 0;
string cmd;

string restore;
string layeractive;

string mkimage( string f ) {
    string ret;
    if (batch) ret += "\nSET CONFIRM YES;";
    sprintf(buf, "\nEXPORT IMAGE '%s.%s' %u;", f, ext, res);
    ret += buf;
    if (batch) ret += "\nSET CONFIRM OFF;";
    return ret;
}

if (argv[1] == "batch") {
    batch = 1;
} else {
    cmd += "WRITE;";
}


if (argc > 1 ) {
    if ( argv[2] == "sch" ) forcefile = 1;
    else if ( argv[2] == "brd" ) forcefile = 2;
}

cmd += "\nSET UNDO_LOG OFF;"; // advisable for speed reasons
cmd += "\nGRID OFF MIL;"; 

if ( forcefile == 1 || ( forcefile == 0 && schematic ) ) project.schematic(SCH) {
    cmd += "\nEDIT .sch;";
    file = SCH.name;
    basefilename = filesetext(SCH.name, "");
    SCH.sheets(S) {
        c++;
        sprintf(buf, "\nEDIT .s%u;", c);
        cmd += buf;
        sprintf(buf, "%s_sheet%u", basefilename, c);
        cmd += mkimage(buf);
    }
} 

if ( forcefile == 2 || ( forcefile == 0 && board )) project.board(B) {
    cmd += "\nEDIT .brd;";
    cmd += "\nSET POLYGON_RATSNEST ON;";
    file = B.name;
    basefilename = filesetext(B.name, "");
    // save color and layer settings
    if (!batch) {
        B.layers(L) {
            if(L.used) {
                sprintf(buf, "\nSET COLOR_LAYER %u %u;", L.number, L.color);
                restore += buf;
                sprintf(buf, "\nSET FILL_LAYER %u %u;", L.number, L.fill);
                restore += buf;
            }
        } 
        for (int i = 0; i< PALETTE_ENTRIES; i++) {
            sprintf(buf, "\nSET palette %u %u;", i, palette(i, PALETTE_COLORED));
            restore += buf;
        }
        switch( palette(-1) ) {
            case 0:
                restore += "\nSET PALETTE BLACK; WINDOW;"; 
                break;
            case 1:
                restore += "\nSET PALETTE WHITE; WINDOW;"; 
                break;
            case 2:
                restore += "\nSET PALETTE COLORED; WINDOW;"; 
                break;
        }
    }
    /*
    // convert layer 20 to polygon
    // problem with holes!
    cmd += "\nCHANGE LAYER 20;";
    int poly_count = 0;
    int poly_current = -1;
    int poly_start_x = 0;
    int poly_start_y = 0;
    B.wires(W) {
        if (W.layer != LAYER_DIMENSION) continue;
        // polygons between two points are not possible, so extract whole paths
        if ( poly_current != poly_count ) {
            poly_current = ++poly_count;
            sprintf(buf, ";\nPOLYGON _OUTLINE_%u_ 0", poly_current);
            cmd += buf;
            poly_start_x = W.x1;
            poly_start_y = W.y1;
            sprintf(buf, " (%f %f) ", u2mil(W.x1), u2mil(W.y1));
            cmd += buf;
        }
        if (! W.arc ) {
            sprintf(buf, " (%f %f) ", u2mil(W.x2), u2mil(W.y2));
            cmd += buf;
            if ( W.x2 == poly_start_x && W.y2 == poly_start_y ) {
                poly_current = -1;
            }
        } else {
        // kreisbogen
            sprintf(buf, "# circle (%f %f) ", u2mil(W.x2), u2mil(W.y2));
            cmd += buf;
        }
        // arc UL_ARC
        // cap int (CAP_...)
        // curve real
        // layer int
        // style int (WIRE_STYLE_...)
        // width int
        // x1, y1 int (Anfangspunkt)
        // x2, y2 int (Endpunkt)
    }
    cmd += ";";
    */
    /* LAYERS:
     *
     * 1 Top            Leiterbahnen oben
     * 2 Route2         Innenlage
     * 3 Route3         Innenlage
     * 4 Route4         Innenlage
     * 5 Route5         Innenlage
     * 6 Route6         Innenlage
     * 7 Route7         Innenlage
     * 8 Route8         Innenlage
     * 9 Route9         Innenlage
     * 10 Route10       Innenlage
     * 11 Route11       Innenlage
     * 12 Route12       Innenlage
     * 13 Route13       Innenlage
     * 14 Route14       Innenlage
     * 15 Route15       Innenlage
     * 16 Bottom        Leiterbahnen unten
     * 17 Pads          Pads (bedrahtete Bauteile)
     * 18 Vias          Vias (durchgehend)
     * 19 Unrouted      Luftlinien
     * 20 Dimension     Platinen-Umrisse (und Kreise für Holes)
     * 21 tPlace        Bestückungsdruck oben
     * 22 bPlace        Bestückungsdruck unten
     * 23 tOrigins      Aufhängepunkte oben (Kreuz automatisch generiert)
     * 24 bOrigins      Aufhängepunkte unten (Kreuz automatisch generiert)
     * 25 tNames        Servicedruck oben (Bauteile-Namen, NAME)
     * 26 bNames        Servicedruck unten (Bauteile-Namen, NAME)
     * 27 tValues       Bauteile-Werte oben (VALUE)
     * 28 bValues       Bauteile-Werte unten (VALUE)
     * 29 tStop         Lötstopmaske oben (automatisch generiert)
     * 30 bStop         Lötstopmaske unten (automatisch generiert)
     * 31 tCream        Lotpaste oben
     * 32 bCream        Lotpaste unten
     * 33 tFinish       Veredelung oben
     * 34 bFinish       Veredelung unten
     * 35 tGlue         Klebemaske oben
     * 36 bGlue         Klebemaske unten
     * 37 tTest         Test- und Abgleichinformationen oben
     * 38 bTest         Test- und Abgleichinformationen unten
     * 39 tKeepout      Sperrflächen für Bauteile oben
     * 40 bKeepout      Sperrflächen für Bauteile unten
     * 41 tRestrict     Sperrflächen für Leiterbahnen oben
     * 42 bRestrict     Sperrflächen für Leiterbahnen unten
     * 43 vRestrict     Sperrflächen für Vias
     * 44 Drills        Bohrungen, durchkontaktiert
     * 45 Holes         Bohrungen, nicht durchkontaktiert
     * 46 Milling       CNC-Fräser-Daten zum Schneiden der Plat.
     * 47 Measures      Bemaßungen
     * 48 Document      allgemeine Dokumentation
     * 49 Reference     Passermarken
     * 51 tDocu         Bauteiledokumentation oben
     * 52 bDocu         Bauteiledokumentation unten
     * 100 DrillBG      Hintergrund in Bohrungen
     */
    // holes to circles

    cmd += "LAYER 100 DrillBG;\n";
    cmd += "CHANGE WIDTH 0;\n"; // filled circles
    B.holes(H) {
        sprintf(buf, "circle (%f %f) (%f %f);\n",
                u2mil(H.x), u2mil(H.y), u2mil(H.x), u2mil((H.drill/2)+H.y));
        cmd += buf;
    }
    // load export colors
    cmd += "\nSCRIPT export-images-colors;";
    cmd += "\nSET Option.LayerSequence 100 20 21 25 31 17 18 1 29 16;";
    // top layer
    cmd += "\nDISPLAY NONE 1 17 18 20 21 25 29 31 46 100;";
    cmd += "\nWINDOW;";
    cmd += "\nRATSNEST;";
    cmd += mkimage(basefilename + "_top");
    // bottom layer
    cmd += "\nDISPLAY NONE 1 16 17 18 20 21 22 23 24 25 26 29 30 39 40 41 42 45 46 47 48 49 100;";
    cmd += "\nWINDOW FIT;";
    cmd += "\nGROUP ALL;";
    cmd += "\nLOCK (CS> 0 0 );";
    cmd += "\nMIRROR (C> 0 0);";
    cmd += "\nGROUP;";
    cmd += "\nDISPLAY NONE 1 17 18 20 21 25 29 31 46 100;";
    cmd += "\nWINDOW;";
    cmd += "\nRATS;";
    cmd += mkimage(basefilename + "_bot");
} 

if (batch) {
    cmd += "\nSET CONFIRM YES;";
}
if (!batch) {
    cmd += restore;
    cmd += "\nSET UNDO_LOG ON;\nGRID LAST;\n";
    cmd += "\nSET CONFIRM NO;";
    cmd += "\nEDIT '" + file + "';";
    cmd += "\nSET CONFIRM OFF;";
} else {
    // save at file close => no!
    cmd += "\nSET CONFIRM NO;";
    cmd += "\nQUIT;";
}

//  EditBox
if (!batch) {
    int Result = dlgDialog("Descriptions") {
        dlgLabel("<b>WARNING</b>");
        dlgLabel( "THIS WILL SAVE YOUR BOARD/SCHEMATIC AT CURRENT STATE AND RELOAD AFTERWARDS,\nWITHOUT ANY HISTORY!");
        dlgHBoxLayout {
            dlgVBoxLayout { dlgSpacing(500); }
            dlgTextEdit(cmd);
        }
        dlgHBoxLayout {
            dlgPushButton("+Execute") dlgAccept();
            dlgSpacing(100);
            dlgPushButton("-Cancel") dlgReject();
        }
    };
    if (Result == 0) exit(0);
}

exit(cmd);

// vim: ft=c
